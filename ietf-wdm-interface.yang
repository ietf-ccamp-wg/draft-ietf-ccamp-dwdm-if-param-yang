module ietf-wdm-interface {
  yang-version 1.1;
  namespace "urn:ietf:params:xml:ns:yang:ietf-wdm-interface";
  prefix wdm-if;

  import ietf-yang-revisions {
    prefix rev;
  }
  import ietf-interfaces {
    prefix if;
  }
  import ietf-layer0-types {
    prefix l0-types;
    rev:recommended-min-date "2025-11-03";
  }

  organization
    "IETF CCAMP Working Group";
  contact
    "WG Web:   <https://datatracker.ietf.org/wg/ccamp/>
     WG List:  <mailto:ccamp@ietf.org>


     Editor: Dharini Hiremagalur <mailto:dharinih@yahoo.com>
     Editor: Gabriele Galimberti <mailto:ggalimbe56@gmail.com>
     Editor: Gert Grammel <mailto:gert.grammel@hpe.com>
     Editor: Roberto Manzotti <mailto:rmanzott@cisco.com>";
  description
    "This module contains a collection of YANG definitions for
     configuring DWDM Optical interfaces.

     Copyright (c) 2025 IETF Trust and the persons identified as
     authors of the code.  All rights reserved.

     Redistribution and use in source and binary forms, with or
     without modification, is permitted pursuant to, and subject
     to the license terms contained in, the Revised BSD
     License set forth in Section 4.c of the IETF Trust's Legal
     Provisions Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed. please:
  // - replace XXXX with actual RFC number of this document
  // - replace ZZZZ with the RFC number assigned to
  //   draft-ietf-ccamp-optical-impairment-topology-yang
  // - replace the revision date with the module publication date
  //   the format is (year-month-day)
  //
  // and finally delete this note.

  revision 2026-10-30 {
    description
      "Initial Version";
    reference
      "RFC XXXX: A YANG data model to manage configurable DWDM
       optical interfaces";
  }

  grouping wdm-if-tca-thresholds {
    description
      "Thresholds for TCA's";
    leaf tca-type {
      type instance-identifier {
        require-instance false;
      }
      must 'count(deref(.)/..
                  | current()/../../..) = 1' {
        error-message
          "The TCA type must reference an attribute of the
           current wdm-interface";
      }
      mandatory true;
      description
        "XPath expression identifying the performance-measurement
         attribute monitored by the TCA. This instance-identifier
         refer to an attribute that MUST be a leaf directly
         contained within the current wdm-interface.
         The associated 'must' statement cannot verify the existence
         of the referenced node in the operational datastore,
         since the operational datastore is not accessible from the
         configuration datastore where this leaf is defined.
         Validation of the existence of the referenced attribute in
         the operational datastore SHALL be performed by the server
         implementation.";
    }
    leaf tca-name {
      type string;
      mandatory true;
      description
        "A textual name of the TCA that explain its scope
         eg 'High-RX-Power'";
    }
    leaf raise-threshold {
      type l0-types:decimal-5;
      must 'current() != ../clear-threshold' {
        error-message
          "TCA raise and clear thresholds must be different";
      }
      mandatory true;
      description
        "A TCA is raised if the variable cross this threshold:
         - if raise-threshold is greater than clear-threshold
         the TCA is raised when the value exceed this threshold
         - if raise-threshold is smaller than clear-threshold, the
         TCA is raised when the value fall below this threshold";
    }
    leaf clear-threshold {
      type l0-types:decimal-5;
      must 'current() != ../raise-threshold' {
        error-message
          "TCA raise and clear thresholds must be different";
      }
      mandatory true;
      description
        "A TCA cleared when the variable cross this threshold:
         - if clear-threshold is smaller than raise-threshold
         the TCA is cleared when the value fall below this threshold
         - if clear-threshold is grater than raise-threshold, the
         TCA is cleared when the value exceed this threshold";
    }
  } // end grouping wdm-if-tca-threshold

  grouping wdm-if-tca-list {
    description
      "List of TCA's";
    leaf number-of-tcas-supported {
      type uint32;
      default "0";
      config false;
      description
        "Number of TCAs supported by this interface,
         if the implementation do not support TCAs it SHALL leave
         this value to default = 0";
    }
    list tca-list {
      key "tca-id";
      description
        "List of the TCAs";
      leaf tca-id {
        type string;
        mandatory true;
        description
          "Unique Identifier of the TCA defined for the interface";
      }
      uses wdm-if-tca-thresholds;
    }
  } // end grouping wdm-if-tca-list

  grouping wdm-if-parameters {
    description
      "DWDM Interface Configuration and Operational parameters";
    leaf central-frequency {
      type l0-types:frequency-thz;
      description
        "This parameter indicates the interface Central Frequency.
         In the configuration datastore the target central-frequency
         configuration can be set/get;
         when reading the operational datastore the implementation
         shall provide the current central-frequency, that may differ
         from the configured value";
      reference
        "ITU-T G.694.1 (10/2020): Spectral grids for WDM
         applications: DWDM frequency grid";
    }
    uses l0-types:common-transceiver-param;
    leaf tx-total-power {
      type l0-types:power-dbm-or-unknown;
      default "unknown";
      config false;
      description
        "The current total transmitted power, if not supported by the
         implementation SHALL not be present";
    }
    leaf cur-osnr {
      type l0-types:snr-or-unknown;
      units "dB";
      default "unknown";
      config false;
      description
        "Current measured Optical Signal to Noise Ratio (OSNR),
         if not supported by the implementation SHALL
         not be present";
    }
    leaf min-osnr-margin {
      type l0-types:snr-or-unknown;
      default "unknown";
      config false;
      description
        "Optical Signal to Noise (OSNR) margin to FEC threshold, if
         not supported by the implementation SHALL remain undefined";
    }
    leaf q-margin {
      type l0-types:decimal-2-or-unknown;
      units "dB";
      default "unknown";
      config false;
      description
        "Q-factor margin to FEC threshold, if not supported by the
         implementationp SHALL remain undefined";
      reference
        "ITU-T O.201 (07/2003): Q-factor test equipment to estimate
                   the transmission performance of optical channels";
    }
    leaf q-factor {
      type l0-types:decimal-2-or-unknown;
      units "dB";
      default "unknown";
      config false;
      description
        "Current measured Q-factor of the interface,
         if not supported by the implementation SHALL
         not be present";
      reference
        "ITU-T O.201 (07/2003): Q-factor test equipment to estimate
                   the transmission performance of optical channels";
    }
    leaf fec-uncorrected-words {
      type uint64;
      config false;
      description
        "Counter of Post-FEC uncorrected errored words,
         if not supported by the implementation SHALL
         not be present";
    }
    leaf fec-uncorrectable-blocks {
      type uint64;
      config false;
      description
        "Counter of the uncorectable FEC data blocks,
         if not supported by the implementation SHALL
         not be present";
    }
    leaf pre-fec-ber {
      type l0-types:decimal-18-or-unknown;
      default "unknown";
      config false;
      description
        "Current measured Pre-FEC error rate,
         if not supported by the implementation SHALL
         not be present";
    }
    leaf chromatic-dispersion {
      type l0-types:decimal-2-or-unknown;
      units "ps/nm";
      default "unknown";
      config false;
      description
        "Chromatic ispersion (CD) on the receive,
         if not supported by the implementation SHALL
         not be present";
      reference
        "RFC ZZZZ: A YANG Data Model for Optical Impairment-aware
                   Topology, Section 2.4.6";
    }
    leaf polarization-mode-dispersion {
      type l0-types:decimal-2-or-unknown;
      units "ps";
      default "unknown";
      config false;
      description
        "Current polarization mode dispersion (PMD) on the receive,
         if not supported by the implementation SHALL
         not be present";
      reference
        "ITU-T G.650.2 (02/2015): Definitions and test methods for
         statistical and non-linear related attributes of
         single-mode fibre and cable. Section 3.1
         RFC ZZZZ: A YANG Data Model for Optical Impairment-aware
                   Topology, Section 2.4.6";
    }
    leaf polarization-dependent-loss {
      type l0-types:power-loss-or-unknown;
      default "unknown";
      config false;
      description
        "Current polarization dependent loss (PDL) on the receive,
         if not supported by the implementation SHALL
         not be present";
      reference
        "RFC ZZZZ: A YANG Data Model for Optical Impairment-aware
                   Topology, Section 2.4.6";
    }
    leaf tx-central-frequency-offset {
      type l0-types:frequency-ghz;
      default "0";
      config false;
      description
        "Frequency difference between nominal and actual optical
         carrier frequency, if not supported by the implementation
         SHALL not be present";
      reference
        "OIF-400GZR-02.0 Implementation Agreement
         Section 13.1";
    }
    leaf rx-central-frequency-offset {
      type l0-types:frequency-ghz;
      default "0";
      config false;
      description
        "Frequency difference between received signal carrier
         frequency and the local laser frequency in coherent
         optical interfaces, if not supported by the implementation
         SHALL not be present";
      reference
        "OIF-400GZR-02.0 Implementation Agreement
         Section 13.1";
    }
    leaf laser-temperature {
      type l0-types:decimal-2-or-unknown;
      units "Deg Celsius";
      default "unknown";
      config false;
      description
        "Laser temperature mesured in degree Celsius,
         if not supported by the implementation SHALL
         not be present";
      reference
        "Openconfig openconfig-platform.yang rev. 0.32.0";
    }
    leaf diff-group-delay {
      type l0-types:decimal-2-or-unknown;
      units "ps";
      default "unknown";
      config false;
      description
        "Transmission delay between polarization modes at the
         reciever, if not supported by the implementation SHALL
         not be present";
      reference
        "OIF-400GZR-02.0 Implementation Agreement
         Section 13.4.7";
    }
    leaf laser-bias-current {
      type l0-types:decimal-2-or-unknown;
      units "mA";
      default "unknown";
      config false;
      description
        "The electircal current applied the the Tx Laser to
         achieve the required output power, expressed in mA,
         if not supported by the implementation SHALL
         not be present";
      reference
        "Openconfig openconfig-platform.yang rev. 0.32.0";
    }
    leaf modulation-error-ratio {
      type l0-types:power-ratio-or-unknown;
      default "unknown";
      config false;
      description
        "Modulation error ratio in dB with two decimal precision.
         if not supported by the implementation SHALL
         not be present";
      reference
        "OIF-400GZR-02.0 Implementation Agreement
         Section 14.4.3";
    }
    leaf tx-variable-optical-attenuation {
      type l0-types:power-ratio-or-unknown;
      default "unknown";
      config false;
      description
        "Variable Optical Attenutor on the TX signal.
         if not supported by the implementation SHALL
         not be present";
      reference
        "TAPI v2.5.0 Reference Implementation Agreement
         TR-547, Table 106";
    }
    leaf rx-variable-optical-attenuation {
      type l0-types:power-ratio-or-unknown;
      default "unknown";
      config false;
      description
        "Variable Optical Attenutor on the RX signal.
         if not supported by the implementation SHALL
         not be present";
      reference
        "TAPI v2.5.0 Reference Implementation Agreement
         TR-547, Table 106";
    }
    leaf max-error-vector-magnitude {
      type l0-types:decimal-5-or-unknown;
      default "unknown";
      config false;
      description
        "EVMmax (Error Vector Magnitude Max) is a metric for
         evaluating maximum error vector magnitude in coherent
         optics, if not supported by the implementation SHALL
         not be present";
      reference
        "OIF-400GZR-02.0 Implementation Agreement
         Section 14.4.1 and 20.1";
    }
    leaf rms-error-vector-magnitude {
      type l0-types:decimal-5-or-unknown;
      default "unknown";
      config false;
      description
        "Error Vector Magnitude normalized by RMS value of
         reference constellation points; used to evaluate
         coherent optical signal quality, if not supported
         by the implementation SHALL not be present";
      reference
        "OIF-400GZR-02.0 Implementation Agreement
         Section 14.4.2";
    }
    leaf second-order-polarization-mode-dispersion {
      type l0-types:decimal-5-or-unknown;
      default "unknown";
      config false;
      description
        "Second Order Polarization Mode Dispersion, if not supported
         by the implementation SHALL not be present";
      reference
        "ITU-T G.650.2 (02/2015): Definitions and test methods for
         statistical and non-linear related attributes of
         single-mode fibre and cable. Section 3.1";
    }
    leaf sop-rate-of-change {
      type l0-types:decimal-5-or-unknown;
      default "unknown";
      config false;
      description
        "Rate of change of polarization state, measured in real-time
         by tracking the speed of polarization state rotation at the
         receiver, if not supported by the implementation SHALL not
         be present";
      reference
        "ITU-T G.698.2 (11/2018): Amplified multichannel dense
         wavelength division multiplexing applications with single
         channel optical interfaces. Section 7.3.7";
    }
    leaf modulation-bias-x-i {
      type l0-types:decimal-2-or-unknown;
      default "unknown";
      config false;
      description
        "Bias on the in-phase (I) path of polarization X in a
         coherent optical modulator, expressed as a percentage, if
         not supported by the implementation SHALL not be present";
      reference
        "Openconfig openconfig-platform.yang rev. 0.32.0";
    }
    leaf modulation-bias-x-q {
      type l0-types:decimal-2-or-unknown;
      default "unknown";
      config false;
      description
        "Bias on the quadrature (Q) path of polarization X in a
         coherent optical modulator, expressed as a percentage, if
         not supported by the implementation SHALL not be present";
      reference
        "Openconfig openconfig-platform.yang rev. 0.32.0l";
    }
    leaf modulation-bias-y-i {
      type l0-types:decimal-2-or-unknown;
      default "unknown";
      config false;
      description
        "Bias on the in-phase (I) path of polarization Y in a
         coherent optical modulator, expressed as a percentage, if
         not supported by the implementation SHALL not be present";
      reference
        "Openconfig openconfig-platform.yang rev. 0.32.0";
    }
    leaf modulation-bias-y-q {
      type l0-types:decimal-2-or-unknown;
      default "unknown";
      config false;
      description
        "Bias on the quadrature (Q) path of polarization Y in a
         coherent optical modulator, expressed as a percentag, if
         not supported by the implementation SHALL not be present";
      reference
        "Openconfig openconfig-platform.yang rev. 0.32.0";
    }
    leaf modulation-bias-x-phase {
      type l0-types:decimal-2-or-unknown;
      default "unknown";
      config false;
      description
        "Bias on the phase path of polarization X in a coherent
         optical modulator, expressed as a percentage, if not
         supported by the implementation SHALL not be present";
      reference
        "Openconfig openconfig-platform.yang rev. 0.32.0";
    }
    leaf modulation-bias-y-phase {
      type l0-types:decimal-2-or-unknown;
      default "unknown";
      config false;
      description
        "Bias on the phase path of polarization Y in a coherent
         optical modulator, expressed as a percentage, if not
         supported by the implementation SHALL not be present";
      reference
        "Openconfig openconfig-platform.yang rev. 0.32.0";
    }
    leaf self-phase-modulation {
      type l0-types:decimal-2-or-unknown;
      default "unknown";
      config false;
      description
        "Self-phase modulation (SPM) is a nonlinear optical effect
         where the phase of a light pulse is modulated by its own
         intensity due to the Kerr effect, if not supported by the
         implementation SHALL not be present";
      reference
        "ITU-T G.650.2 (02/2015): Definitions and test methods for
         statistical and non-linear related attributes of
         single-mode fibre and cable. Section II.3.1";
    }
    leaf cross-phase-modulation {
      type l0-types:decimal-2-or-unknown;
      default "unknown";
      config false;
      description
        "Cross-phase modulation (XPM) is a nonlinear optical effect
         where the intensity of one light signal modulates the phase
         of another signal traveling through the same fiber, if not
         supported by the implementation SHALL not be present";
      reference
        "ITU-T G.650.2 (02/2015): Definitions and test methods for
         statistical and non-linear related attributes of
         single-mode fibre and cable. Section II.3.3";
    }
  } // end grouping wdm-if-parameters

  notification wdm-if-tca {
    description
      "A notification for a Threshold Crossing Alert (TCA)";
    leaf if-name {
      type leafref {
        path "/if:interfaces/if:interface/if:name";
      }
      mandatory true;
      description
        "Interface name";
    }
    leaf tca-type {
      type instance-identifier {
        require-instance false;
      }
      mandatory true;
      description
        "XPath expression identifying the performance-measurement
         attribute monitored by the TCA that triggered the
         notification";
    }
    leaf tca-name {
      type string;
      mandatory true;
      description
        "A textual name of the TCA that have triggered the
         notification that explain its scope, eg 'TX Power Degrade'";
    }
  } // end notification wdm-if-tca

  augment "/if:interfaces" {
    description
      "Template definition for Optical Interface explicit-modes";
    container wdm-if-templates {
      config false;
      description
        "Optical Interface explicit-mode templates";
      container explicit-transceiver-modes {
        description
          "The top level container for the list of the
           transceivers' explicit modes.";
        list explicit-transceiver-mode {
          key "explicit-transceiver-mode-id";
          description
            "The list of the transceivers' explicit modes.";
          leaf explicit-transceiver-mode-id {
            type string {
              length "8..64";
            }
            description
              "The identifier of the transceivers' explicit mode.";
          }
          uses l0-types:explicit-mode;
        } // end list explicit-transceiver-mode
      } // end container explicit-transceiver-modes
    } // end container wdm-if-templates
  } // end augmentation interfaces

  augment "/if:interfaces/if:interface" {
    description
      "Parameters for an optical interface";
    container wdm-interface {
      description
        "Container for capabilities, configuration,
         current operational data for a DWDM interface";
      uses l0-types:transceiver-capabilities {
        augment "supported-modes/supported-mode/mode/"
              + "explicit-mode/explicit-mode" {
          description
            "Augment the explicit-mode container with the
             proper leafref.";
          leaf explicit-transceiver-mode-ref {
            type leafref {
              path "../../../../../../wdm-if:wdm-if-templates"
                 + "/wdm-if:explicit-transceiver-modes"
                 + "/wdm-if:explicit-transceiver-mode"
                 + "/wdm-if:explicit-transceiver-mode-id";
            }
            config false;
            mandatory true;
            description
              "The reference to the explicit transceiver
               mode template.";
          } // end explicit-transceiver-mode-ref
        } // end augmentation explicit-mode
      } // end uses l0-types:transceiver-capabilities
      container wdm-if-tcas {
        description
          "Threshold Crossing Alerts definition and configuration";
        uses wdm-if-tca-list;
      } // end of container wdm-if-tcas
      leaf configured-mode {
        type union {
          type empty;
          type leafref {
            path "../supported-modes/supported-mode/mode-id";
            require-instance false;
          }
        }
        default "empty";
        description
          "Reference to the configured mode for transceiver
           compatibility approach.

           The empty value is used to report that no mode has
           been configured and there is no default mode.

           When not present, the configured-mode is not reported
           by the server, this means the interface is not
           configured";
      }
      uses wdm-if-parameters;
    } // end container wdm-interface
  } // end augmentation interface
}
